UMINHO-GR-MIB DEFINITIONS ::= BEGIN

IMPORTS
	experimental,
	MODULE-IDENTITY,
	OBJECT-TYPE
		FROM SNMPv2-SMI
	DisplayString
		FROM SNMPv2-TC
	OBJECT-GROUP
		FROM SNMPv2-CONF;

unpredictableMIB MODULE-IDENTITY
	LAST-UPDATED "201701301238Z"
	ORGANIZATION "University of Minho"
	CONTACT-INFO
		"- Bruno Pereira a72628@alunos.uminho.pt"
	DESCRIPTION
		"MIB for a random number generation server. This type of remote service over the internet will be available to other systems that need ways to get random numbers, where the latter are not controlled by internal processes, to their own computer system."
	REVISION "201701301238Z"
	DESCRIPTION
		"Initial version."

	-- 1.3.6.1.3.99
	::= { experimental 99 }





unpredictableTable OBJECT-GROUP
	OBJECTS {
		indexRandHexNumber,
		randomHexadecimalNumber }
	STATUS  current
	DESCRIPTION
		"Group with table of N random numbers;"
	-- 1.3.6.1.3.99.3.1.1
	::= { unpredictableMIB 1 }

unpredictableParam OBJECT-GROUP
	OBJECTS {
		paramR,
		paramD,
		paramN,
		paramAuthReset }
	STATUS  current
	DESCRIPTION
		"Group with scalar objects that represent the operating parameters;"
	-- 1.3.6.1.3.99.3.1.2
	::= { unpredictableMIB 2 }

paramR OBJECT-TYPE
	SYNTAX  INTEGER (1..1000)
	UNITS	"Hz"
	MAX-ACCESS read-only
	STATUS  current
	DESCRIPTION
		"Frequency R of refreshing the table of random numbers (in Hz);"
	-- 1.3.6.1.3.99.1.3
	::= { unpredictableParam 1 }


paramN OBJECT-TYPE
	SYNTAX  INTEGER (1..1000)
	MAX-ACCESS read-only
	STATUS  current
	DESCRIPTION
		"N number of entries in the random number table;"
	-- 1.3.6.1.3.99.4
	::= { unpredictableParam 2 }


paramD OBJECT-TYPE
	SYNTAX  INTEGER (1..1000)
	MAX-ACCESS read-only
	STATUS  current
	DESCRIPTION
		"Number of D hexadecimal digits of each entry in the random number table;"
	-- 1.3.6.1.3.99.5
	::= { unpredictableParam 3 }


paramAuthReset OBJECT-TYPE
	SYNTAX  DisplayString
	MAX-ACCESS read-write
	STATUS  current
	DESCRIPTION
		"Authorizations for the agent reset operation."
	-- 1.3.6.1.3.99.6
	::= { unpredictableParam 4 }


randomTable OBJECT-TYPE
	SYNTAX  SEQUENCE OF RandomTableEntry
	MAX-ACCESS not-accessible
	STATUS  current
	DESCRIPTION
		"This is the table used for storage of random sequence of hexadecimal digits"
	-- 1.3.6.1.3.99.7
	::= { unpredictableTable 1 }

randomTableEntry OBJECT-TYPE
	SYNTAX  RandomTableEntry
	MAX-ACCESS not-accessible
	STATUS  current
	DESCRIPTION
		"An entry for the information about a specific random hexadecimal digit"
	INDEX {
		indexRandHexNumber }
	::= { randomTable 1 }


RandomTableEntry ::= SEQUENCE {

	indexRandHexNumber      INTEGER,
	randomHexadecimalNumber DisplayString }



indexRandHexNumber OBJECT-TYPE
	SYNTAX  INTEGER (1..1000)
	MAX-ACCESS read-only
	STATUS  current
	DESCRIPTION
		"Index for the entry of the random hexadecimal number of the table"
	-- 1.3.6.1.3.99.1.7.1.1
	::= { randomTableEntry 1 }


randomHexadecimalNumber OBJECT-TYPE
	SYNTAX  DisplayString
	MAX-ACCESS read-write
	STATUS  current
	DESCRIPTION
		"Sequence of D hexadecimal digits."
	-- 1.3.6.1.3.99.1.7.1.2
	::= { randomTableEntry 2 }




END
